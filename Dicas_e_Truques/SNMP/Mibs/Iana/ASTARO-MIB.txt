ASTARO-MIB DEFINITIONS ::= BEGIN

--
-- Astaro Notification Definition
--
-- .1.3.6.1.4.1.9789
-- .iso.org.dod.internet.private.enterprises.astaro
--      .1500  (.notification)
--           .0  (DEBUG)
--           .1  (INFO)
--           .2  (WARN)
--           .3  (CRIT)
--                .0 - .999   (<notificationID>)
--      .1501  (.notificationGroup)
--

IMPORTS
    MODULE-IDENTITY, OBJECT-TYPE, NOTIFICATION-TYPE,
    enterprises
             FROM SNMPv2-SMI
     NOTIFICATION-GROUP
             FROM SNMPv2-CONF ;


--
-- top level
--

astaro MODULE-IDENTITY
    LAST-UPDATED "201605060000Z"
    ORGANIZATION "Sophos Ltd"
    CONTACT-INFO
                 "Sophos Ltd.
                 The Pentagon
                 Abingdon Science Park
                 Abingdon OX14 3YP
                 United Kingdom

                 Phone: +44 (0)1235 559933
                 Email: customercare@sophos.com
                 www.sophos.com"
    DESCRIPTION
                 "The MIB module for Notification Events

                 Copyright (C) 2009,2016 by Sophos Ltd."
    REVISION     "201605060000Z"
    DESCRIPTION
                 "Change descriptors to conform to RFC 2578"
    REVISION     "200812170000Z"
    DESCRIPTION
                 "Initial version"
::= { enterprises 9789 }

notification OBJECT IDENTIFIER ::= { astaro 1500 }
notificationGroup OBJECT IDENTIFIER ::= { astaro 1501 }


--
-- Notification severity
--

debug OBJECT IDENTIFIER ::= { notification 0 }
info  OBJECT IDENTIFIER ::= { notification 1 }
warn  OBJECT IDENTIFIER ::= { notification 2 }
crit  OBJECT IDENTIFIER ::= { notification 3 }


-- 
-- Notifications
--
sophosUTMNotificationsBASE NOTIFICATION-GROUP
       NOTIFICATIONS { sophosUTMNotificationCRIT025, sophosUTMNotificationCRIT026, sophosUTMNotificationCRIT054, sophosUTMNotificationCRIT060, sophosUTMNotificationCRIT065, sophosUTMNotificationINFO000, sophosUTMNotificationINFO005, sophosUTMNotificationINFO006, sophosUTMNotificationINFO007, sophosUTMNotificationINFO010, sophosUTMNotificationINFO011, sophosUTMNotificationINFO020, sophosUTMNotificationINFO021, sophosUTMNotificationINFO022, sophosUTMNotificationINFO040, sophosUTMNotificationINFO050, sophosUTMNotificationINFO051, sophosUTMNotificationINFO053, sophosUTMNotificationINFO062, sophosUTMNotificationINFO063, sophosUTMNotificationINFO065, sophosUTMNotificationINFO094, sophosUTMNotificationINFO095, sophosUTMNotificationINFO601, sophosUTMNotificationWARN005, sophosUTMNotificationWARN006, sophosUTMNotificationWARN007, sophosUTMNotificationWARN025, sophosUTMNotificationWARN030, sophosUTMNotificationWARN031, sophosUTMNotificationWARN032, sophosUTMNotificationWARN033, sophosUTMNotificationWARN040, sophosUTMNotificationWARN052, sophosUTMNotificationWARN061, sophosUTMNotificationWARN070, sophosUTMNotificationWARN094, sophosUTMNotificationWARN136, sophosUTMNotificationWARN201, sophosUTMNotificationWARN531, sophosUTMNotificationWARN600, sophosUTMNotificationWARN602, sophosUTMNotificationWARN603, sophosUTMNotificationWARN604 }
       STATUS        current
       DESCRIPTION
               "Notification category Base System"
      ::= { notificationGroup 0 }

sophosUTMNotificationsSELFMON NOTIFICATION-GROUP
       NOTIFICATIONS { sophosUTMNotificationINFO105, sophosUTMNotificationINFO106, sophosUTMNotificationINFO107, sophosUTMNotificationINFO108, sophosUTMNotificationINFO109, sophosUTMNotificationINFO110, sophosUTMNotificationINFO111, sophosUTMNotificationINFO112, sophosUTMNotificationINFO114, sophosUTMNotificationINFO115, sophosUTMNotificationINFO116, sophosUTMNotificationINFO117, sophosUTMNotificationINFO118, sophosUTMNotificationINFO119, sophosUTMNotificationINFO120, sophosUTMNotificationINFO121, sophosUTMNotificationINFO122, sophosUTMNotificationINFO123, sophosUTMNotificationINFO124, sophosUTMNotificationINFO125, sophosUTMNotificationINFO126, sophosUTMNotificationINFO127, sophosUTMNotificationINFO128, sophosUTMNotificationINFO129, sophosUTMNotificationINFO130, sophosUTMNotificationINFO131, sophosUTMNotificationINFO132, sophosUTMNotificationINFO133, sophosUTMNotificationINFO134, sophosUTMNotificationINFO135, sophosUTMNotificationINFO136, sophosUTMNotificationINFO138, sophosUTMNotificationINFO139, sophosUTMNotificationINFO140, sophosUTMNotificationINFO141, sophosUTMNotificationINFO142, sophosUTMNotificationINFO143, sophosUTMNotificationINFO144, sophosUTMNotificationINFO145, sophosUTMNotificationINFO146, sophosUTMNotificationINFO147, sophosUTMNotificationINFO148, sophosUTMNotificationINFO149, sophosUTMNotificationINFO150, sophosUTMNotificationINFO152, sophosUTMNotificationINFO153, sophosUTMNotificationINFO154, sophosUTMNotificationINFO163, sophosUTMNotificationINFO164, sophosUTMNotificationINFO170, sophosUTMNotificationINFO171, sophosUTMNotificationINFO172, sophosUTMNotificationINFO173, sophosUTMNotificationINFO175, sophosUTMNotificationINFO176, sophosUTMNotificationINFO177, sophosUTMNotificationINFO178, sophosUTMNotificationINFO179, sophosUTMNotificationINFO180, sophosUTMNotificationINFO181, sophosUTMNotificationINFO182, sophosUTMNotificationINFO183, sophosUTMNotificationINFO184, sophosUTMNotificationINFO185, sophosUTMNotificationINFO186, sophosUTMNotificationINFO187, sophosUTMNotificationINFO188, sophosUTMNotificationINFO189, sophosUTMNotificationINFO190, sophosUTMNotificationINFO191, sophosUTMNotificationINFO192, sophosUTMNotificationINFO193, sophosUTMNotificationINFO194, sophosUTMNotificationWARN129, sophosUTMNotificationWARN160, sophosUTMNotificationWARN161, sophosUTMNotificationWARN162 }
       STATUS        current
       DESCRIPTION
               "Notification category Selfmonitor"
      ::= { notificationGroup 1 }

sophosUTMNotificationsUP2DATE NOTIFICATION-GROUP
       NOTIFICATIONS { sophosUTMNotificationCRIT310, sophosUTMNotificationCRIT311, sophosUTMNotificationINFO301, sophosUTMNotificationINFO302, sophosUTMNotificationINFO306, sophosUTMNotificationINFO310, sophosUTMNotificationINFO320, sophosUTMNotificationINFO321, sophosUTMNotificationINFO322 }
       STATUS        current
       DESCRIPTION
               "Notification category Up2Date"
      ::= { notificationGroup 2 }

sophosUTMNotificationsREPORTING NOTIFICATION-GROUP
       NOTIFICATIONS { sophosUTMNotificationCRIT712, sophosUTMNotificationINFO700, sophosUTMNotificationINFO710, sophosUTMNotificationINFO720, sophosUTMNotificationINFO721, sophosUTMNotificationINFO722, sophosUTMNotificationINFO723, sophosUTMNotificationINFO724, sophosUTMNotificationINFO725, sophosUTMNotificationINFO726, sophosUTMNotificationINFO727, sophosUTMNotificationINFO728, sophosUTMNotificationINFO729, sophosUTMNotificationWARN711, sophosUTMNotificationWARN715, sophosUTMNotificationWARN726, sophosUTMNotificationWARN727, sophosUTMNotificationWARN728, sophosUTMNotificationWARN729 }
       STATUS        current
       DESCRIPTION
               "Notification category Logging / Reporting"
      ::= { notificationGroup 4 }

sophosUTMNotificationsIPS NOTIFICATION-GROUP
       NOTIFICATIONS { sophosUTMNotificationCRIT850, sophosUTMNotificationCRIT852, sophosUTMNotificationCRIT861, sophosUTMNotificationINFO850, sophosUTMNotificationINFO852, sophosUTMNotificationINFO870, sophosUTMNotificationWARN850, sophosUTMNotificationWARN852, sophosUTMNotificationWARN856 }
       STATUS        current
       DESCRIPTION
               "Notification category Intrusion Prevention"
      ::= { notificationGroup 5 }

sophosUTMNotificationsHA NOTIFICATION-GROUP
       NOTIFICATIONS { sophosUTMNotificationCRIT027, sophosUTMNotificationCRIT028, sophosUTMNotificationCRIT080, sophosUTMNotificationCRIT081, sophosUTMNotificationCRIT082, sophosUTMNotificationCRIT090, sophosUTMNotificationCRIT091, sophosUTMNotificationCRIT092, sophosUTMNotificationINFO080, sophosUTMNotificationINFO081, sophosUTMNotificationINFO083, sophosUTMNotificationINFO090, sophosUTMNotificationINFO091, sophosUTMNotificationINFO092, sophosUTMNotificationINFO093, sophosUTMNotificationWARN080, sophosUTMNotificationWARN090 }
       STATUS        current
       DESCRIPTION
               "Notification category HA / Cluster"
      ::= { notificationGroup 6 }

sophosUTMNotificationsEPP NOTIFICATION-GROUP
       NOTIFICATIONS { sophosUTMNotificationWARN501 }
       STATUS        current
       DESCRIPTION
               "Notification category Endpoint"
      ::= { notificationGroup 7 }

sophosUTMNotificationCRIT025 NOTIFICATION-TYPE
    STATUS current
    DESCRIPTION
          "License usage: EXCEEDING 100% OF USER COUNT on Sophos UTM"
::= { crit 25 }

sophosUTMNotificationCRIT026 NOTIFICATION-TYPE
    STATUS current
    DESCRIPTION
          "License usage: EXCEEDING 110% OF USER COUNT on Sophos UTM"
::= { crit 26 }

sophosUTMNotificationCRIT027 NOTIFICATION-TYPE
    STATUS current
    DESCRIPTION
          "License usage: No valid HA license"
::= { crit 27 }

sophosUTMNotificationCRIT028 NOTIFICATION-TYPE
    STATUS current
    DESCRIPTION
          "License usage: No valid Cluster license"
::= { crit 28 }

sophosUTMNotificationCRIT054 NOTIFICATION-TYPE
    STATUS current
    DESCRIPTION
          "UPS power critical, system shutting down"
::= { crit 54 }

sophosUTMNotificationCRIT060 NOTIFICATION-TYPE
    STATUS current
    DESCRIPTION
          "Raid degraded: harddisk replacement needed"
::= { crit 60 }

sophosUTMNotificationCRIT065 NOTIFICATION-TYPE
    STATUS current
    DESCRIPTION
          "IPv6 Renumbering failed"
::= { crit 65 }

sophosUTMNotificationCRIT080 NOTIFICATION-TYPE
    STATUS current
    DESCRIPTION
          "HA System: There is no slave node, please check your HA System"
::= { crit 80 }

sophosUTMNotificationCRIT081 NOTIFICATION-TYPE
    STATUS current
    DESCRIPTION
          "HA System: Your installed system versions differ, please check your HA System"
::= { crit 81 }

sophosUTMNotificationCRIT082 NOTIFICATION-TYPE
    STATUS current
    DESCRIPTION
          "HA System: Some interfaces are unplugged, please check your HA System"
::= { crit 82 }

sophosUTMNotificationCRIT090 NOTIFICATION-TYPE
    STATUS current
    DESCRIPTION
          "Cluster: One or more nodes are dead, please check your Cluster"
::= { crit 90 }

sophosUTMNotificationCRIT091 NOTIFICATION-TYPE
    STATUS current
    DESCRIPTION
          "Cluster: Your installed system versions differ, please check your Cluster"
::= { crit 91 }

sophosUTMNotificationCRIT092 NOTIFICATION-TYPE
    STATUS current
    DESCRIPTION
          "Cluster: Some interfaces are unplugged, please check your Cluster"
::= { crit 92 }

sophosUTMNotificationCRIT310 NOTIFICATION-TYPE
    STATUS current
    DESCRIPTION
          "Up2Date prefetch failed"
::= { crit 310 }

sophosUTMNotificationCRIT311 NOTIFICATION-TYPE
    STATUS current
    DESCRIPTION
          "Firmware Up2Date installation failed"
::= { crit 311 }

sophosUTMNotificationCRIT712 NOTIFICATION-TYPE
    STATUS current
    DESCRIPTION
          "System shut down due to full log file partition"
::= { crit 712 }

sophosUTMNotificationCRIT850 NOTIFICATION-TYPE
    STATUS current
    DESCRIPTION
          "Intrusion Prevention Alert"
::= { crit 850 }

sophosUTMNotificationCRIT852 NOTIFICATION-TYPE
    STATUS current
    DESCRIPTION
          "Intrusion Prevention Alert (Packet dropped)"
::= { crit 852 }

sophosUTMNotificationCRIT861 NOTIFICATION-TYPE
    STATUS current
    DESCRIPTION
          "Advanced Threat Protection Alert"
::= { crit 861 }

sophosUTMNotificationINFO000 NOTIFICATION-TYPE
    STATUS current
    DESCRIPTION
          "System was restarted"
::= { info 0 }

sophosUTMNotificationINFO005 NOTIFICATION-TYPE
    STATUS current
    DESCRIPTION
          "Successful WebAdmin login"
::= { info 5 }

sophosUTMNotificationINFO006 NOTIFICATION-TYPE
    STATUS current
    DESCRIPTION
          "Successful SSH login"
::= { info 6 }

sophosUTMNotificationINFO007 NOTIFICATION-TYPE
    STATUS current
    DESCRIPTION
          "Successful console login"
::= { info 7 }

sophosUTMNotificationINFO010 NOTIFICATION-TYPE
    STATUS current
    DESCRIPTION
          "Configuration Auto Backup"
::= { info 10 }

sophosUTMNotificationINFO011 NOTIFICATION-TYPE
    STATUS current
    DESCRIPTION
          "Configuration Backup File"
::= { info 11 }

sophosUTMNotificationINFO020 NOTIFICATION-TYPE
    STATUS current
    DESCRIPTION
          "License expiry: a feature will expire"
::= { info 20 }

sophosUTMNotificationINFO021 NOTIFICATION-TYPE
    STATUS current
    DESCRIPTION
          "License expiry: a feature expires today"
::= { info 21 }

sophosUTMNotificationINFO022 NOTIFICATION-TYPE
    STATUS current
    DESCRIPTION
          "License expiry: a feature expired"
::= { info 22 }

sophosUTMNotificationINFO040 NOTIFICATION-TYPE
    STATUS current
    DESCRIPTION
          "Remote Configuration Manager - System Information"
::= { info 40 }

sophosUTMNotificationINFO050 NOTIFICATION-TYPE
    STATUS current
    DESCRIPTION
          "UPS device connected"
::= { info 50 }

sophosUTMNotificationINFO051 NOTIFICATION-TYPE
    STATUS current
    DESCRIPTION
          "UPS device disconnected"
::= { info 51 }

sophosUTMNotificationINFO053 NOTIFICATION-TYPE
    STATUS current
    DESCRIPTION
          "UPS power restored"
::= { info 53 }

sophosUTMNotificationINFO062 NOTIFICATION-TYPE
    STATUS current
    DESCRIPTION
          "Raid rebuild process started"
::= { info 62 }

sophosUTMNotificationINFO063 NOTIFICATION-TYPE
    STATUS current
    DESCRIPTION
          "Raid rebuild process finished"
::= { info 63 }

sophosUTMNotificationINFO065 NOTIFICATION-TYPE
    STATUS current
    DESCRIPTION
          "IPv6 Renumbering successful"
::= { info 65 }

sophosUTMNotificationINFO080 NOTIFICATION-TYPE
    STATUS current
    DESCRIPTION
          "HA node is now Master"
::= { info 80 }

sophosUTMNotificationINFO081 NOTIFICATION-TYPE
    STATUS current
    DESCRIPTION
          "HA node is now Slave"
::= { info 81 }

sophosUTMNotificationINFO083 NOTIFICATION-TYPE
    STATUS current
    DESCRIPTION
          "HA System is active and fully functional"
::= { info 83 }

sophosUTMNotificationINFO090 NOTIFICATION-TYPE
    STATUS current
    DESCRIPTION
          "Cluster node is now Master"
::= { info 90 }

sophosUTMNotificationINFO091 NOTIFICATION-TYPE
    STATUS current
    DESCRIPTION
          "Cluster node is now Slave"
::= { info 91 }

sophosUTMNotificationINFO092 NOTIFICATION-TYPE
    STATUS current
    DESCRIPTION
          "Cluster node is now Worker"
::= { info 92 }

sophosUTMNotificationINFO093 NOTIFICATION-TYPE
    STATUS current
    DESCRIPTION
          "Cluster is active and fully functional"
::= { info 93 }

sophosUTMNotificationINFO094 NOTIFICATION-TYPE
    STATUS current
    DESCRIPTION
          "Upgrade: download successful"
::= { info 94 }

sophosUTMNotificationINFO095 NOTIFICATION-TYPE
    STATUS current
    DESCRIPTION
          "RED Unlock code"
::= { info 95 }

sophosUTMNotificationINFO105 NOTIFICATION-TYPE
    STATUS current
    DESCRIPTION
          "User Authenticator not running - restarted"
::= { info 105 }

sophosUTMNotificationINFO106 NOTIFICATION-TYPE
    STATUS current
    DESCRIPTION
          "Cron Task Scheduler not running - restarted"
::= { info 106 }

sophosUTMNotificationINFO107 NOTIFICATION-TYPE
    STATUS current
    DESCRIPTION
          "WebAdmin webserver not running - restarted"
::= { info 107 }

sophosUTMNotificationINFO108 NOTIFICATION-TYPE
    STATUS current
    DESCRIPTION
          "Ssh server not running - restarted"
::= { info 108 }

sophosUTMNotificationINFO109 NOTIFICATION-TYPE
    STATUS current
    DESCRIPTION
          "Dhcp client not running - restarted"
::= { info 109 }

sophosUTMNotificationINFO110 NOTIFICATION-TYPE
    STATUS current
    DESCRIPTION
          "Configuration daemon not running - restarted"
::= { info 110 }

sophosUTMNotificationINFO111 NOTIFICATION-TYPE
    STATUS current
    DESCRIPTION
          "Syslog server not running - restarted"
::= { info 111 }

sophosUTMNotificationINFO112 NOTIFICATION-TYPE
    STATUS current
    DESCRIPTION
          "Middleware not running - restarted"
::= { info 112 }

sophosUTMNotificationINFO114 NOTIFICATION-TYPE
    STATUS current
    DESCRIPTION
          "Ulogd not running - restarted"
::= { info 114 }

sophosUTMNotificationINFO115 NOTIFICATION-TYPE
    STATUS current
    DESCRIPTION
          "Snort not running - restarted"
::= { info 115 }

sophosUTMNotificationINFO116 NOTIFICATION-TYPE
    STATUS current
    DESCRIPTION
          "Snmpd daemon not running - restarted"
::= { info 116 }

sophosUTMNotificationINFO117 NOTIFICATION-TYPE
    STATUS current
    DESCRIPTION
          "Pop3 proxy not running - restarted"
::= { info 117 }

sophosUTMNotificationINFO118 NOTIFICATION-TYPE
    STATUS current
    DESCRIPTION
          "Ftp proxy not running - restarted"
::= { info 118 }

sophosUTMNotificationINFO119 NOTIFICATION-TYPE
    STATUS current
    DESCRIPTION
          "Named not running - restarted"
::= { info 119 }

sophosUTMNotificationINFO120 NOTIFICATION-TYPE
    STATUS current
    DESCRIPTION
          "Sockd not running - restarted"
::= { info 120 }

sophosUTMNotificationINFO121 NOTIFICATION-TYPE
    STATUS current
    DESCRIPTION
          "Identd not running - restarted"
::= { info 121 }

sophosUTMNotificationINFO122 NOTIFICATION-TYPE
    STATUS current
    DESCRIPTION
          "Dhcpd not running - restarted"
::= { info 122 }

sophosUTMNotificationINFO123 NOTIFICATION-TYPE
    STATUS current
    DESCRIPTION
          "IRQd not running - restarted"
::= { info 123 }

sophosUTMNotificationINFO124 NOTIFICATION-TYPE
    STATUS current
    DESCRIPTION
          "Ufod not running - restarted"
::= { info 124 }

sophosUTMNotificationINFO125 NOTIFICATION-TYPE
    STATUS current
    DESCRIPTION
          "Smtpd not running - restarted"
::= { info 125 }

sophosUTMNotificationINFO126 NOTIFICATION-TYPE
    STATUS current
    DESCRIPTION
          "Dyndns not running - restarted"
::= { info 126 }

sophosUTMNotificationINFO127 NOTIFICATION-TYPE
    STATUS current
    DESCRIPTION
          "Spam filter not running - restarted"
::= { info 127 }

sophosUTMNotificationINFO128 NOTIFICATION-TYPE
    STATUS current
    DESCRIPTION
          "Pptpd not running - restarted"
::= { info 128 }

sophosUTMNotificationINFO129 NOTIFICATION-TYPE
    STATUS current
    DESCRIPTION
          "IPv6 Watchdog not running - restarted"
::= { info 129 }

sophosUTMNotificationINFO130 NOTIFICATION-TYPE
    STATUS current
    DESCRIPTION
          "Winbindd not running - restarted"
::= { info 130 }

sophosUTMNotificationINFO131 NOTIFICATION-TYPE
    STATUS current
    DESCRIPTION
          "Xinetd not running - restarted"
::= { info 131 }

sophosUTMNotificationINFO132 NOTIFICATION-TYPE
    STATUS current
    DESCRIPTION
          "ACC core daemon not running - restarted"
::= { info 132 }

sophosUTMNotificationINFO133 NOTIFICATION-TYPE
    STATUS current
    DESCRIPTION
          "ACC up2date cache not running - restarted"
::= { info 133 }

sophosUTMNotificationINFO134 NOTIFICATION-TYPE
    STATUS current
    DESCRIPTION
          "IPsec starter not running - restarted"
::= { info 134 }

sophosUTMNotificationINFO135 NOTIFICATION-TYPE
    STATUS current
    DESCRIPTION
          "IPsec pluto not running - restarted"
::= { info 135 }

sophosUTMNotificationINFO136 NOTIFICATION-TYPE
    STATUS current
    DESCRIPTION
          "ACC device agent not running - restarted"
::= { info 136 }

sophosUTMNotificationINFO138 NOTIFICATION-TYPE
    STATUS current
    DESCRIPTION
          "Smtp scan daemon not running - restarted"
::= { info 138 }

sophosUTMNotificationINFO139 NOTIFICATION-TYPE
    STATUS current
    DESCRIPTION
          "Content Filter Framework not running - restarted"
::= { info 139 }

sophosUTMNotificationINFO140 NOTIFICATION-TYPE
    STATUS current
    DESCRIPTION
          "Notification Daemon not running - restarted"
::= { info 140 }

sophosUTMNotificationINFO141 NOTIFICATION-TYPE
    STATUS current
    DESCRIPTION
          "Http proxy not running - restarted"
::= { info 141 }

sophosUTMNotificationINFO142 NOTIFICATION-TYPE
    STATUS current
    DESCRIPTION
          "OSPF daemon (ospfd) not running - restarted"
::= { info 142 }

sophosUTMNotificationINFO143 NOTIFICATION-TYPE
    STATUS current
    DESCRIPTION
          "Dynamic routing daemon (quagga) not running - restarted"
::= { info 143 }

sophosUTMNotificationINFO144 NOTIFICATION-TYPE
    STATUS current
    DESCRIPTION
          "HAL (Hardware Abstraction Layer) system daemon not running - restarted"
::= { info 144 }

sophosUTMNotificationINFO145 NOTIFICATION-TYPE
    STATUS current
    DESCRIPTION
          "Udev (system device manager) daemon not running - restarted"
::= { info 145 }

sophosUTMNotificationINFO146 NOTIFICATION-TYPE
    STATUS current
    DESCRIPTION
          "Dbus (application device bus) system daemon not running - restarted"
::= { info 146 }

sophosUTMNotificationINFO147 NOTIFICATION-TYPE
    STATUS current
    DESCRIPTION
          "NTP (network time synchronization) daemon not running - restarted"
::= { info 147 }

sophosUTMNotificationINFO148 NOTIFICATION-TYPE
    STATUS current
    DESCRIPTION
          "L2TP-over-IPsec daemon not running - restarted"
::= { info 148 }

sophosUTMNotificationINFO149 NOTIFICATION-TYPE
    STATUS current
    DESCRIPTION
          "Application Control daemon not running - restarted"
::= { info 149 }

sophosUTMNotificationINFO150 NOTIFICATION-TYPE
    STATUS current
    DESCRIPTION
          "Root partition is filling up - please check"
::= { info 150 }

sophosUTMNotificationINFO152 NOTIFICATION-TYPE
    STATUS current
    DESCRIPTION
          "Network Monitor not running - restarted"
::= { info 152 }

sophosUTMNotificationINFO153 NOTIFICATION-TYPE
    STATUS current
    DESCRIPTION
          "Log Disk is filling up - please check"
::= { info 153 }

sophosUTMNotificationINFO154 NOTIFICATION-TYPE
    STATUS current
    DESCRIPTION
          "Data Disk is filling up - please check"
::= { info 154 }

sophosUTMNotificationINFO163 NOTIFICATION-TYPE
    STATUS current
    DESCRIPTION
          "Log Disk is short of inodes - please check"
::= { info 163 }

sophosUTMNotificationINFO164 NOTIFICATION-TYPE
    STATUS current
    DESCRIPTION
          "Data Disk is short of inodes - please check"
::= { info 164 }

sophosUTMNotificationINFO170 NOTIFICATION-TYPE
    STATUS current
    DESCRIPTION
          "HA confd sync daemon not running - restarted"
::= { info 170 }

sophosUTMNotificationINFO171 NOTIFICATION-TYPE
    STATUS current
    DESCRIPTION
          "HA up2date proxy not running - restarted"
::= { info 171 }

sophosUTMNotificationINFO172 NOTIFICATION-TYPE
    STATUS current
    DESCRIPTION
          "HA conntrack daemon not running - restarted"
::= { info 172 }

sophosUTMNotificationINFO173 NOTIFICATION-TYPE
    STATUS current
    DESCRIPTION
          "HA csync2 daemon not running - restarted"
::= { info 173 }

sophosUTMNotificationINFO175 NOTIFICATION-TYPE
    STATUS current
    DESCRIPTION
          "IPv6 Teredo Tunnel Broker client not running - restarted"
::= { info 175 }

sophosUTMNotificationINFO176 NOTIFICATION-TYPE
    STATUS current
    DESCRIPTION
          "IPv6 gogo6 Tunnel Broker client not running - restarted"
::= { info 176 }

sophosUTMNotificationINFO177 NOTIFICATION-TYPE
    STATUS current
    DESCRIPTION
          "IPv6 Routing Advertisement daemon not running - restarted"
::= { info 177 }

sophosUTMNotificationINFO178 NOTIFICATION-TYPE
    STATUS current
    DESCRIPTION
          "IPv6 Hurricane Tunnel Broker client not running - restarted"
::= { info 178 }

sophosUTMNotificationINFO179 NOTIFICATION-TYPE
    STATUS current
    DESCRIPTION
          "DNS resolver not running - restarted"
::= { info 179 }

sophosUTMNotificationINFO180 NOTIFICATION-TYPE
    STATUS current
    DESCRIPTION
          "Client Authentication daemon not running - restarted"
::= { info 180 }

sophosUTMNotificationINFO181 NOTIFICATION-TYPE
    STATUS current
    DESCRIPTION
          "Service Monitor not running - restarted"
::= { info 181 }

sophosUTMNotificationINFO182 NOTIFICATION-TYPE
    STATUS current
    DESCRIPTION
          "Job queue manager (atd) not running - restarted"
::= { info 182 }

sophosUTMNotificationINFO183 NOTIFICATION-TYPE
    STATUS current
    DESCRIPTION
          "BGP daemon (bgpd) not running - restarted"
::= { info 183 }

sophosUTMNotificationINFO184 NOTIFICATION-TYPE
    STATUS current
    DESCRIPTION
          "RED server not running - restarted"
::= { info 184 }

sophosUTMNotificationINFO185 NOTIFICATION-TYPE
    STATUS current
    DESCRIPTION
          "RED client not running - restarted"
::= { info 185 }

sophosUTMNotificationINFO186 NOTIFICATION-TYPE
    STATUS current
    DESCRIPTION
          "Confd request queuer not running - restarted"
::= { info 186 }

sophosUTMNotificationINFO187 NOTIFICATION-TYPE
    STATUS current
    DESCRIPTION
          "Confd queue runner not running - restarted"
::= { info 187 }

sophosUTMNotificationINFO188 NOTIFICATION-TYPE
    STATUS current
    DESCRIPTION
          "urid not running - restarted"
::= { info 188 }

sophosUTMNotificationINFO189 NOTIFICATION-TYPE
    STATUS current
    DESCRIPTION
          "Web Application Firewall not running - restarted"
::= { info 189 }

sophosUTMNotificationINFO190 NOTIFICATION-TYPE
    STATUS current
    DESCRIPTION
          "Support access daemon not running - restarted"
::= { info 190 }

sophosUTMNotificationINFO191 NOTIFICATION-TYPE
    STATUS current
    DESCRIPTION
          "RPM database restored"
::= { info 191 }

sophosUTMNotificationINFO192 NOTIFICATION-TYPE
    STATUS current
    DESCRIPTION
          "RRD cache daemon not running - restarted"
::= { info 192 }

sophosUTMNotificationINFO193 NOTIFICATION-TYPE
    STATUS current
    DESCRIPTION
          "REST daemon not running - restarted"
::= { info 193 }

sophosUTMNotificationINFO194 NOTIFICATION-TYPE
    STATUS current
    DESCRIPTION
          "oculusd not running - restarted"
::= { info 194 }

sophosUTMNotificationINFO301 NOTIFICATION-TYPE
    STATUS current
    DESCRIPTION
          "New Firmware Up2Date is ready for installation"
::= { info 301 }

sophosUTMNotificationINFO302 NOTIFICATION-TYPE
    STATUS current
    DESCRIPTION
          "New Firmware Up2Date installed"
::= { info 302 }

sophosUTMNotificationINFO306 NOTIFICATION-TYPE
    STATUS current
    DESCRIPTION
          "New Pattern Up2Dates installed"
::= { info 306 }

sophosUTMNotificationINFO310 NOTIFICATION-TYPE
    STATUS current
    DESCRIPTION
          "Up2Date prefetch is working again"
::= { info 310 }

sophosUTMNotificationINFO320 NOTIFICATION-TYPE
    STATUS current
    DESCRIPTION
          "Database Conversion Started"
::= { info 320 }

sophosUTMNotificationINFO321 NOTIFICATION-TYPE
    STATUS current
    DESCRIPTION
          "Database Conversion Adjourned"
::= { info 321 }

sophosUTMNotificationINFO322 NOTIFICATION-TYPE
    STATUS current
    DESCRIPTION
          "Database Conversion Finished"
::= { info 322 }

sophosUTMNotificationINFO601 NOTIFICATION-TYPE
    STATUS current
    DESCRIPTION
          "Your Hotspot password"
::= { info 601 }

sophosUTMNotificationINFO700 NOTIFICATION-TYPE
    STATUS current
    DESCRIPTION
          "Daily log file archive"
::= { info 700 }

sophosUTMNotificationINFO710 NOTIFICATION-TYPE
    STATUS current
    DESCRIPTION
          "Log file partition is filling up"
::= { info 710 }

sophosUTMNotificationINFO720 NOTIFICATION-TYPE
    STATUS current
    DESCRIPTION
          "Daily Executive Report"
::= { info 720 }

sophosUTMNotificationINFO721 NOTIFICATION-TYPE
    STATUS current
    DESCRIPTION
          "Weekly Executive Report"
::= { info 721 }

sophosUTMNotificationINFO722 NOTIFICATION-TYPE
    STATUS current
    DESCRIPTION
          "Monthly Executive Report"
::= { info 722 }

sophosUTMNotificationINFO723 NOTIFICATION-TYPE
    STATUS current
    DESCRIPTION
          "Daily Executive Report"
::= { info 723 }

sophosUTMNotificationINFO724 NOTIFICATION-TYPE
    STATUS current
    DESCRIPTION
          "Weekly Executive Report"
::= { info 724 }

sophosUTMNotificationINFO725 NOTIFICATION-TYPE
    STATUS current
    DESCRIPTION
          "Monthly Executive Report"
::= { info 725 }

sophosUTMNotificationINFO726 NOTIFICATION-TYPE
    STATUS current
    DESCRIPTION
          "VPN connection using Site-to-Site is up again"
::= { info 726 }

sophosUTMNotificationINFO727 NOTIFICATION-TYPE
    STATUS current
    DESCRIPTION
          "RED connection is up again"
::= { info 727 }

sophosUTMNotificationINFO728 NOTIFICATION-TYPE
    STATUS current
    DESCRIPTION
          "Access Point is online again"
::= { info 728 }

sophosUTMNotificationINFO729 NOTIFICATION-TYPE
    STATUS current
    DESCRIPTION
          "Mesh Access Point is online again"
::= { info 729 }

sophosUTMNotificationINFO850 NOTIFICATION-TYPE
    STATUS current
    DESCRIPTION
          "Intrusion Prevention Alert"
::= { info 850 }

sophosUTMNotificationINFO852 NOTIFICATION-TYPE
    STATUS current
    DESCRIPTION
          "Intrusion Prevention Alert (Packet dropped)"
::= { info 852 }

sophosUTMNotificationINFO870 NOTIFICATION-TYPE
    STATUS current
    DESCRIPTION
          "Sandbox Event triggered"
::= { info 870 }

sophosUTMNotificationWARN005 NOTIFICATION-TYPE
    STATUS current
    DESCRIPTION
          "Failed WebAdmin login"
::= { warn 5 }

sophosUTMNotificationWARN006 NOTIFICATION-TYPE
    STATUS current
    DESCRIPTION
          "Failed SSH login"
::= { warn 6 }

sophosUTMNotificationWARN007 NOTIFICATION-TYPE
    STATUS current
    DESCRIPTION
          "Failed console login"
::= { warn 7 }

sophosUTMNotificationWARN025 NOTIFICATION-TYPE
    STATUS current
    DESCRIPTION
          "License usage: EXCEEDING 90% OF USER COUNT on Sophos UTM"
::= { warn 25 }

sophosUTMNotificationWARN030 NOTIFICATION-TYPE
    STATUS current
    DESCRIPTION
          "Primary internet uplink is down, switching to backup line"
::= { warn 30 }

sophosUTMNotificationWARN031 NOTIFICATION-TYPE
    STATUS current
    DESCRIPTION
          "Primary internet uplink is back online, switching to main line"
::= { warn 31 }

sophosUTMNotificationWARN032 NOTIFICATION-TYPE
    STATUS current
    DESCRIPTION
          "Internet uplink is down"
::= { warn 32 }

sophosUTMNotificationWARN033 NOTIFICATION-TYPE
    STATUS current
    DESCRIPTION
          "Internet uplink is up again"
::= { warn 33 }

sophosUTMNotificationWARN040 NOTIFICATION-TYPE
    STATUS current
    DESCRIPTION
          "Sophos UTM weak Certificate check - found weak certificates"
::= { warn 40 }

sophosUTMNotificationWARN052 NOTIFICATION-TYPE
    STATUS current
    DESCRIPTION
          "UPS on battery power"
::= { warn 52 }

sophosUTMNotificationWARN061 NOTIFICATION-TYPE
    STATUS current
    DESCRIPTION
          "Raid degraded: defective harddisk inserted"
::= { warn 61 }

sophosUTMNotificationWARN070 NOTIFICATION-TYPE
    STATUS current
    DESCRIPTION
          "Too many failed logins"
::= { warn 70 }

sophosUTMNotificationWARN080 NOTIFICATION-TYPE
    STATUS current
    DESCRIPTION
          "HA selfcheck"
::= { warn 80 }

sophosUTMNotificationWARN090 NOTIFICATION-TYPE
    STATUS current
    DESCRIPTION
          "Cluster selfcheck"
::= { warn 90 }

sophosUTMNotificationWARN094 NOTIFICATION-TYPE
    STATUS current
    DESCRIPTION
          "Upgrade failed"
::= { warn 94 }

sophosUTMNotificationWARN129 NOTIFICATION-TYPE
    STATUS current
    DESCRIPTION
          "Spam Filter cannot query database servers"
::= { warn 129 }

sophosUTMNotificationWARN136 NOTIFICATION-TYPE
    STATUS current
    DESCRIPTION
          "ACC server not reachable"
::= { warn 136 }

sophosUTMNotificationWARN160 NOTIFICATION-TYPE
    STATUS current
    DESCRIPTION
          "Root partition is short of inodes - please check"
::= { warn 160 }

sophosUTMNotificationWARN161 NOTIFICATION-TYPE
    STATUS current
    DESCRIPTION
          "RPM Database is corrupted"
::= { warn 161 }

sophosUTMNotificationWARN162 NOTIFICATION-TYPE
    STATUS current
    DESCRIPTION
          "Corrupted RPM database rebuild failed"
::= { warn 162 }

sophosUTMNotificationWARN201 NOTIFICATION-TYPE
    STATUS current
    DESCRIPTION
          "A RED device has been deauthorized automatically"
::= { warn 201 }

sophosUTMNotificationWARN501 NOTIFICATION-TYPE
    STATUS current
    DESCRIPTION
          "Endpoint Virus Detected"
::= { warn 501 }

sophosUTMNotificationWARN531 NOTIFICATION-TYPE
    STATUS current
    DESCRIPTION
          "Directory Services synchronization"
::= { warn 531 }

sophosUTMNotificationWARN600 NOTIFICATION-TYPE
    STATUS current
    DESCRIPTION
          "Certificate(s) will expire"
::= { warn 600 }

sophosUTMNotificationWARN602 NOTIFICATION-TYPE
    STATUS current
    DESCRIPTION
          "Let's Encrypt Terms of Service are expired"
::= { warn 602 }

sophosUTMNotificationWARN603 NOTIFICATION-TYPE
    STATUS current
    DESCRIPTION
          "Let's Encrypt certificate renewal failed accessing Let's Encrypt service"
::= { warn 603 }

sophosUTMNotificationWARN604 NOTIFICATION-TYPE
    STATUS current
    DESCRIPTION
          "Let's Encrypt certificate renewal failed"
::= { warn 604 }

sophosUTMNotificationWARN711 NOTIFICATION-TYPE
    STATUS current
    DESCRIPTION
          "Log files have been deleted"
::= { warn 711 }

sophosUTMNotificationWARN715 NOTIFICATION-TYPE
    STATUS current
    DESCRIPTION
          "Remote log file storage failed"
::= { warn 715 }

sophosUTMNotificationWARN726 NOTIFICATION-TYPE
    STATUS current
    DESCRIPTION
          "VPN connection using Site-to-Site is down"
::= { warn 726 }

sophosUTMNotificationWARN727 NOTIFICATION-TYPE
    STATUS current
    DESCRIPTION
          "RED connection is down"
::= { warn 727 }

sophosUTMNotificationWARN728 NOTIFICATION-TYPE
    STATUS current
    DESCRIPTION
          "Access Point is offline"
::= { warn 728 }

sophosUTMNotificationWARN729 NOTIFICATION-TYPE
    STATUS current
    DESCRIPTION
          "Mesh Access Point is offline"
::= { warn 729 }

sophosUTMNotificationWARN850 NOTIFICATION-TYPE
    STATUS current
    DESCRIPTION
          "Intrusion Prevention Alert"
::= { warn 850 }

sophosUTMNotificationWARN852 NOTIFICATION-TYPE
    STATUS current
    DESCRIPTION
          "Intrusion Prevention Alert (Packet dropped)"
::= { warn 852 }

sophosUTMNotificationWARN856 NOTIFICATION-TYPE
    STATUS current
    DESCRIPTION
          "Portscan detected"
::= { warn 856 }



END
